/* SPDX-FileCopyrightText: 2026 Elan8
 * SPDX-License-Identifier: MIT */
package KitchenTimerNavigation {
    doc /*
     * Navigation only. The selected product occurrence is
     * KitchenTimerSystem::kitchenTimer.
     */
    alias systemOfInterest for KitchenTimerSystem::kitchenTimer;

    private import KitchenTimerSystem;
    private import UserInterfaceSystem;
    private import ControlSystem;
    private import PowerSystem;
    private import MechanicalAssemblySystem;
    private import KitchenTimerContext;
    private import KitchenTimerUseCases;
    private import KitchenTimerStakeholderRequirements;
    private import KitchenTimerLibrary;
    private import KitchenTimerDocuments;
}
